module srl_nokia-next-hop-groups {

    yang-version 1.1;

    // namespace
    namespace "urn:srl_nokia/next-hop-groups";

    prefix "srl_nokia-next-hop-groups";

    import srl_nokia-common { prefix srl_nokia-comm; }
    import srl_nokia-network-instance { prefix srl_nokia-netinst; }

    description
        "This yang file gives a description of next-hop-groups configuration.";

    revision 2019-11-30 {
        description
      "SRLinux 19.11.1";
    }

    grouping next-hop-group-top {
        container next-hop-groups {
            presence "Configure Nexthop Groups";
            list group {
                key "name";
                description "Specifies the next hop group.";
                leaf name {
                    type srl_nokia-comm:name;
                    description
                        "Specifies the next hop group name";
                }
                leaf admin-state {
                    type srl_nokia-comm:admin-state;
                    default "enable";
                    description
                        "Used to enable or disable a next-hop group";
                }
                leaf collect-stats {
                    type boolean;
                    default false;
                    description
                        "When set to true a stats resource is used to count the number of packets/octets forwarded to each next-hop in this next-hop-group";
                }
                container blackhole {
                    presence "Specifies that the next-hop-group performs a blackhole discard action.";
                    leaf generate-icmp {
                        type boolean;
                        default false;
                        description
                            "When set to true the router generates ICMP unreachable messages for the dropped packets";
                    }
                }
                list nexthop {
                    max-elements 128;
                    key "index";
                    leaf index {
                        type uint16;
                        description
                            "Numerical index of the next-hop member";
                    }
                    leaf ip-address {
                        type srl_nokia-comm:ip-address;
                        description
                            "The next-hop IPv4 or IPv6 address";
                    }
                    leaf admin-state {
                        type srl_nokia-comm:admin-state;
                        default "enable";
                        description
                            "Used to enable or disable a particular next-hop";
                    }
                    leaf resolve {
                        type boolean;
                        default true;
                        description
                            "When set to true, the router is allowed to use any route to resolve the nexthop address to an outgoing interface

                            When set to false the router is only allowed to use a local route to resolve the next-hop address.";
                    }
                    leaf-list pushed-mpls-label-stack {
                        type srl_nokia-comm:mpls-label;
                        max-elements 1;
                        description
                            "A list of MPLS labels to push onto the packet when forwarding to this particular next-hop

                            Default is none/empty. Pushing an MPLS label stack is not supported unless the resolve flag is set to false.";
                    }
                }
            }
        }
    }
    augment "/srl_nokia-netinst:network-instance" {
        uses next-hop-group-top;
    }
}
