module srl_nokia-interfaces {
  yang-version 1.1;
  namespace "urn:srl_nokia/interfaces";
  prefix srl_nokia-if;

  // import some basic types

  import srl_nokia-common {
    prefix srl_nokia-comm;
  }
  import srl_nokia-if-ip {
    prefix srl_nokia-if-ip;
  }
  import srl_nokia-extensions {
    prefix srl_nokia-ext;
  }

  description
    "Model for managing network interfaces and subinterfaces.

    This model reuses data items defined in the IETF YANG model for
    interfaces described by RFC 7223";

  revision 2019-11-30 {
    description
      "SRLinux 19.11.1";
  }

  // typedef statements

  typedef port-oper-down-reason {
    type enumeration {
      enum "port-admin-disabled";
      enum "mda-admin-disabled";
      enum "transceiver-admin-disabled";
      enum "loopback";
      enum "port-not-present";
      enum "mda-not-present";
      enum "transceiver-not-present";
      enum "phy-initializing";
      enum "lower-layer-down";
      enum "mtu-resource-exceeded";
      enum "unsupported-speed";
      enum "invalid-transceiver-fec";
      enum "other";
      enum "fabric-availability";
    }
  }

  typedef subif-oper-down-reason {
    type enumeration {
      enum "admin-disabled";
      enum "port-down";
      enum "mtu-resource-exceeded";
      enum "mtu-too-large";
      enum "no-ip-config";
      enum "other";
    }
  }

  typedef transceiver-oper-state {
    type enumeration {
      enum "up";
      enum "down";
      enum "not-present";
    }
  }

  typedef interface-id {
    type string;
    description
      "User-defined identifier for an interface, generally used to name a interface reference. The id can be arbitrary but a useful convention is to use a combination of base interface name and subinterface index.";
  }

  // grouping statements

  grouping interface-common-config {
    description
      "Configuration data nodes common to physical interfaces and subinterfaces";
    leaf description {
      type srl_nokia-comm:description;
      description
        "A user-configured description of the interface";
      reference "RFC 2863: The Interfaces Group MIB - ifAlias";
    }
    leaf admin-state {
      srl_nokia-ext:show-importance high;
      type srl_nokia-comm:admin-state;
      default "enable";
      description
        "The configured, desired state of the interface";
      reference "RFC 2863: The Interfaces Group MIB - ifAdminStatus";
    }
  }

  grouping interface-phys-config {
    description
      "Configuration data for physical interfaces";
    uses interface-common-config;
    leaf mtu {
      type uint16 {
          range "1500..9500";
      }
      units bytes;
      description
        "Port MTU in bytes including ethernet overhead but excluding 4-bytes FCS

        If a packet exceeds this size it is dropped.

        Each linecard supports a maximum of 8 different port MTU values. The default value for a network port is taken from /system/mtu/default-port-mtu. The port MTU is not configurable for loopback and management ports.";
    }
// DTS 338272 - remove loopback-mode support for 19.11 release
//    leaf loopback-mode {
//      type boolean;
//      description
//        "When loopback-mode is set to true the port loops back packets that come in via the port";
      // TO-DO: must not be a mgmt0 or loN interface
//    }
  }

  grouping subinterface-config {
    description
      "Configuration data for subinterfaces";
    uses interface-common-config;

    leaf ip-mtu {
      type uint16 {
        range "1280..9486";
      }
      units bytes;
      description
        "IP MTU of the subinterface in bytes, including the IP header but excluding Ethernet encapsulation

        IP MTU specifies the maximum sized IPv4 or IPv6 packet that can be transmitted on the subinterface. If an IPv4 or IPv6 packet exceeds this size it is dropped and this may result in the generation of an ICMP error message back to the source.

        Each linecard supports a maximum of 4 different IP MTU values. The default value for a subinterface is taken from /system/mtu/default-ip-mtu. The IP MTU is not configurable for subinterfaces of loopback and management ports.";
    }
  }

  grouping subinterface-top {
    description
      "Subinterface data for logical interfaces associated with a given interface";
    list subinterface {
      max-elements 4;
      key "index";
      description
        "The list of subinterfaces (logical interfaces) associated with a physical interface";
      leaf index {
        type uint32 {
          range "0..9999";
        }
        description
          "The index of the subinterface, or logical interface number";
      }
      uses subinterface-config;
      leaf name {
        config false;
        type string;
        description
          "The system assigned name of the subinterface. It is formed by taking the base interface name and appending a dot (.) and the subinterface index number. For example, ethernet-2/1.0";
      }
      leaf oper-state {
        srl_nokia-ext:show-importance high;
        config false;
        type enumeration {
          enum "up";
          enum "down";
        }
        description
          "The operational state of the subinterface";
        // Corresponds to ifOperStatus from the IFMIB.
      }
      leaf oper-down-reason {
        config false;
        srl_nokia-ext:show-importance "high";
        type subif-oper-down-reason;
        description
          "The first (and possibly only) reason for the subinterface being operationally down";
      }
      leaf last-change {
        config false;
        type srl_nokia-comm:date-and-time-delta;
        description
          "The date and time of the most recent change to the subinterface state";
        // Corresponds to ifLastChange from the IF-MIB.
      }
      uses srl_nokia-if-ip:ipv4-top;
      uses srl_nokia-if-ip:ipv6-top;
      uses srl_nokia-if-ip:subinterface-statistics;
    }
  }

  grouping interface-top {
    description
      "Top-level grouping for interface configuration and operational state data";
    list interface {
      key "name";
      description
        "The list of named interfaces on the device.";

      leaf name {
        type srl_nokia-comm:interface-all;
        description
          "The name of the interface

          Valid options are:
          mgmt<N>, N=0
          mgmt<N>-standby, N=0
          lo<N>, N=0..255
          ethernet-<slot>/<port>
          ethernet-<slot>/<mda>/<port>
          ethernet-<slot>/<connector>/<lane>
          ethernet-<slot>/<mda>/<connector>/<lane>

          <slot>=slot number {1,2,3,..}
          <mda>=mda id {a,b,c,d}
          <connector>=connector id {1,2,3,..}
          <port>=port id {1,2,3,..}
          <lane>=channel or breakout port id {1,2,3,..}";
        }
      uses interface-phys-config;
      leaf ifindex {
        config false;
        type uint32;
        description
          "System-wide persistent unique ifIndex assigned to the interface";
      }
      leaf oper-state {
        srl_nokia-ext:show-importance high;
        config false;
        type enumeration {
          enum "up";
          enum "down";
        }
        description
          "The operational state of the interface";
      }
      leaf oper-down-reason {
        config false;
        srl_nokia-ext:show-importance "high";
        type port-oper-down-reason;
        description
          "The first (and possibly only) reason for the port being operationally down";
      }
      leaf last-change {
        config false;
        type srl_nokia-comm:date-and-time-delta;
        description
          "The date and time of the most recent change to the interface state";
        // Corresponds to ifLastChange from the IF-MIB.
      }
      container statistics {
        config false;
        leaf in-octets {
          type srl_nokia-comm:zero-based-counter64;
          description
            "Corresponds to ifHCInOctets from the IFMIB.";
        }
        leaf in-unicast-packets {
          type srl_nokia-comm:zero-based-counter64;
          description
            "Corresponds to ifHCInUcastPkts from the IF-MIB.";
        }
        leaf in-broadcast-packets {
          type srl_nokia-comm:zero-based-counter64;
          description
            "Corresponds to ifHCInBroadcastPkts from the IF-MIB.";
        }
        leaf in-multicast-packets {
          type srl_nokia-comm:zero-based-counter64;
          description
            "Corresponds to ifHCInMulticastPkts from the IF-MIB.";
        }
        /* leaf in-discards {
          type srl_nokia-comm:zero-based-counter64;
          description
            "Corresponds to ifInDiscards from the IFMIB.";
        } */
        leaf in-error-packets {
          type srl_nokia-comm:zero-based-counter64;
          description
            "Corresponds to ifInErrors from the IF-MIB.";
        }
        /* leaf in-unknown-protos {
          type srl_nokia-comm:zero-based-counter64;
          description
            "Corresponds to ifInUnknownProtos from the IF-MIB.";
        } */
        leaf in-fcs-error-packets {
          type srl_nokia-comm:zero-based-counter64;
          description
            "Ingress FCS errors.";
        }
        leaf out-octets {
          type srl_nokia-comm:zero-based-counter64;
          description
            "Corresponds to ifHCOutOctetsfrom the IF-MIB.";
        }
        leaf out-unicast-packets {
          type srl_nokia-comm:zero-based-counter64;
          description
            "Corresponds to ifHCOutUcastPktsfrom the IF-MIB.";
        }
        leaf out-broadcast-packets {
          type srl_nokia-comm:zero-based-counter64;
          description
            "Corresponds to ifHCOutBroadcastPkts from the IF-MIB.";
        }
        leaf out-multicast-packets {
          type srl_nokia-comm:zero-based-counter64;
          description
            "Corresponds to ifHCOutMulticastPkts from the IF-MIB.";
        }
        /* leaf out-discards {
          type srl_nokia-comm:zero-based-counter64;
          description
            "Corresponds to ifOutDiscards from the IF-MIB.";
        } */
        leaf out-error-packets {
          type srl_nokia-comm:zero-based-counter64;
          description
            "Corresponds to ifOutErrors from the IF-MIB.";
        }
        leaf carrier-transitions {
          type srl_nokia-comm:zero-based-counter64;
          description
            "Number of times the interface state has transitioned from down to up since the time the device restarted or the last clear.";
        }
        leaf last-clear {
          type srl_nokia-comm:date-and-time-delta;
          description
            "Timestamp of the last time the interface counters were cleared.";
        }
      }
      container traffic-rate {
        config false;
        description
          "Container for traffic rate statistics";
        leaf in-bps {
          type uint64;
          description
            "The ingress bandwidth utilization of the port, updated every 10 seconds";
        }
        leaf out-bps {
          type uint64;
          description
            "The egress bandwidth utilization of the port, updated every 10 seconds";
        }
      }
      container transceiver {
        leaf admin-state {
          type srl_nokia-comm:admin-state;
          // default "enable";
          description
            "The configured, desired state of the transceiver";
        }
        leaf oper-state {
          config false;
          type transceiver-oper-state;
          description
            "The operational state of the transceiver";
        }
        leaf ddm-events {
          type boolean;
          description
            "When set to true, log events and state related to the Digital Diagnostic Monitoring (DDM) capabilities of the transceiver are generated and populated.

            When set to false, no DDM-related log events and state are generated and populated for this port/transceiver.

            Default is false (for interfaces that support transceivers).";
        }
        leaf forward-error-correction {
            type enumeration {
                enum "disabled";
                enum "rs-528";
                enum "rs-544";
            }
            // default "none";
            description
                "The forward error correction algorithm to use on the optical channel

                100G interfaces support disabled and rs-528 as valid options that do not bring the port down.

                400G interfaces support rs-544 as the only valid option that does not bring the port down.";
        }
        leaf form-factor {
          config false;
          type enumeration {
            enum CFP2 {
              value 1;
            }
            enum CFP2-ACO {
              value 2;
            }
            enum CFP4 {
              value 3;
            }
            enum QSFP {
              value 4;
            }
            enum QSFPplus {
              value 5;
            }
            enum QSFP28 {
              value 6;
            }
            enum QSFPDD {
              value 7;
            }
            enum SFP {
              value 8;
            }
            enum SFPplus {
              value 9;
            }
            enum Non-pluggable {
              value 10;
            }
            enum Other {
              value 11;
            }
          }
          description
            "Specifies the transceiver form factor associated with the port.";
          // (NOTE - may not be complete)
        }
        leaf ethernet-pmd {
          config false;
          type string;
          description
            "Specifies the Ethernet compliance code of the transceiver associated with the port.";
        }
        leaf connector-type {
          config false;
          type enumeration {
            enum SC {
              value 1;
            }
            enum LC {
              value 2;
            }
            enum MPO-1x12 {
              value 3;
            }
            enum no-separable-connector {
              value 4;
            }
            enum unknown {
              value 5;
            }
          }
          description
            "Specifies the fiber connector type of the transceiver associated with the port.";
        }
        leaf vendor {
          config false;
          type string;
          description
            "Name of the transceiver vendor.";
        }
        leaf vendor-part-number {
          config false;
          type string;
          description
            "Vendor's part number for the transceiver.";
        }
        leaf vendor-revision {
          config false;
          type string;
          description
            "Vendor's revision number for the transceiver.";
        }
        leaf serial-number {
          config false;
          type string;
          description
            "Transceiver serial number.";
        }
        leaf date-code {
          config false;
          type string;
          description
            "Transceiver date code.";
        }
        leaf fault-condition {
          config false;
          type boolean;
          description
            "Indicates if a fault condition exists in the transceiver.";
        }
        container temperature {
          config false;
          leaf latest-value {
            type srl_nokia-comm:temperature;
            description
              "The current temperature of the transceiver module in degrees Celsius";
          }
          leaf high-alarm-condition {
            type boolean;
            description
              "Set to true whenever the temperature is above the high-alarm-threshold and set to false whenever the temperature is below the high-alarm-threshold";
          }
          leaf high-alarm-threshold {
            type srl_nokia-comm:temperature;
            description
              "Read from the installed transceiver";
          }
          leaf low-alarm-condition {
            type boolean;
            description
              "Set to true whenever the temperature is below the low-alarm-threshold and set to false whenever the temperature is above the low-alarm-threshold";
          }
          leaf low-alarm-threshold {
            type srl_nokia-comm:temperature;
            description
              "Read from the installed transceiver";
          }
          leaf high-warning-condition {
            type boolean;
            description
              "Set to true whenever the temperature is above the high-warning-threshold and set to false whenever the temperature is below the high-warning-threshold";
          }
          leaf high-warning-threshold {
            type srl_nokia-comm:temperature;
            description
              "Read from the installed transceiver";
          }
          leaf low-warning-condition {
            type boolean;
            description
              "Set to true whenever the temperature is below the low-warning-threshold and set to false whenever the temperature is above the low-warning-threshold";
          }
          leaf low-warning-threshold {
            type srl_nokia-comm:temperature;
            description
              "Read from the installed transceiver";
          }
        }
        container voltage {
          config false;
          leaf latest-value {
            type decimal64 {
              fraction-digits 4;
            }
            description
              "The current voltage reading of the transceiver module (in Volts)";
          }
          leaf high-alarm-condition {
            type boolean;
            description
              "Set to true whenever the module voltage is above the high-alarm-threshold and set to false whenever the module voltage is below the high-alarm-threshold";
          }
          leaf high-alarm-threshold {
            type decimal64 {
              fraction-digits 4;
            }
            description
              "Read from the installed transceiver";
          }
          leaf low-alarm-condition {
            type boolean;
            description
              "Set to true whenever the module voltage is below the low-alarm-threshold and set to false whenever the module voltage is above the low-alarm-threshold";
          }
          leaf low-alarm-threshold {
            type decimal64 {
              fraction-digits 4;
            }
            description
              "Read from the installed transceiver";
          }
          leaf high-warning-condition {
            type boolean;
            description
              "Set to true whenever the module voltage is above the high-warning-threshold and set to false whenever the module voltage is below the high-warning-threshold";
          }
          leaf high-warning-threshold {
            type decimal64 {
              fraction-digits 4;
            }
            description
              "Read from the installed transceiver";
          }
          leaf low-warning-condition {
            type boolean;
            description
              "Set to true whenever the module voltage is below the low-warning-threshold and set to false whenever the module voltage is above the low-warning-threshold";
          }
          leaf low-warning-threshold {
            type decimal64 {
              fraction-digits 4;
            }
            description
              "Read from the installed transceiver";
          }
        }
        list channel {
          config false;
          description
            "List of physical channels supported by the transceiver that are associated with this particular port";
          key "index";
          leaf index {
            type uint8 {
              range "1..10";
            }
            description
              "Index of the physical channel or lane";
          }
          leaf wavelength {
            config false;
            type decimal64 {
              fraction-digits 2;
            }
            description
              "Wavelength of the transmitting laser in nanometers";
          }
          container input-power {
            config false;
            leaf latest-value {
              type decimal64 {
                fraction-digits 2;
              }
              description
                "The current value of the optical Rx power in dBm";
            }
            leaf high-alarm-condition {
              type boolean;
              description
                "Set to true whenever the Rx power is above the high-alarm-threshold and set to false whenever the Rx power is below the high-alarm-threshold";
            }
            leaf high-alarm-threshold {
              type decimal64 {
                fraction-digits 2;
              }
              description
                "Read from the installed transceiver";
            }
            leaf low-alarm-condition {
              type boolean;
              description
                "Set to true whenever the Rx power is below the low-alarm-threshold and set to false whenever the Rx power is above the low-alarm-threshold";
            }
            leaf low-alarm-threshold {
              type decimal64 {
                fraction-digits 2;
              }
              description
                "Read from the installed transceiver";
            }
            leaf high-warning-condition {
              type boolean;
              description
                "Set to true whenever the Rx power is above the high-warning-threshold and set to false whenever the Rx power is below the high-warning-threshold";
            }
            leaf high-warning-threshold {
              type decimal64 {
                fraction-digits 2;
              }
              description
                "Read from the installed transceiver";
            }
            leaf low-warning-condition {
              type boolean;
              description
                "Set to true whenever the Rx power is below the low-warning-threshold and set to false whenever the Rx power is above the low-warning-threshold";
            }
            leaf low-warning-threshold {
              type decimal64 {
                fraction-digits 2;
              }
              description
                "Read from the installed transceiver";
            }
          }
          container output-power {
            config false;
            leaf latest-value {
              type decimal64 {
                fraction-digits 2;
              }
              description
                "The current value of the optical Tx power in dBm";
            }
            leaf high-alarm-condition {
              type boolean;
              description
                "Set to true whenever the Tx power is above the high-alarm-threshold and set to false whenever the Tx power is below the high-alarm-threshold";
            }
            leaf high-alarm-threshold {
              type decimal64 {
                fraction-digits 2;
              }
              description
                "Read from the installed transceiver";
            }
            leaf low-alarm-condition {
              type boolean;
              description
                "Set to true whenever the Tx power is below the low-alarm-threshold and set to false whenever the Tx power is above the low-alarm-threshold";
            }
            leaf low-alarm-threshold {
              type decimal64 {
                fraction-digits 2;
              }
              description
                "Read from the installed transceiver";
            }
            leaf high-warning-condition {
              type boolean;
              description
                "Set to true whenever the Tx power is above the high-warning-threshold and set to false whenever the Tx power is below the high-warning-threshold";
            }
            leaf high-warning-threshold {
              type decimal64 {
                fraction-digits 2;
              }
              description
                "Read from the installed transceiver";
            }
            leaf low-warning-condition {
              type boolean;
              description
                "Set to true whenever the Tx power is below the low-warning-threshold and set to false whenever the Tx power is above the low-warning-threshold";
            }
            leaf low-warning-threshold {
              type decimal64 {
                fraction-digits 2;
              }
              description
                "Read from the installed transceiver";
            }
          }
          container laser-bias-current {
            config false;
            leaf latest-value {
              type decimal64 {
                fraction-digits 3;
              }
              description
                "The current value of the laser bias current in mA";
            }
            leaf high-alarm-condition {
              type boolean;
              description
                "Set to true whenever the laser bias current is above the high-alarm-threshold and set to false whenever the laser bias current is below the high-alarm-threshold";
            }
            leaf high-alarm-threshold {
              type decimal64 {
                fraction-digits 3;
              }
              description
                "Read from the installed transceiver";
            }
            leaf low-alarm-condition {
              type boolean;
              description
                "Set to true whenever the laser bias current is below the low-alarm-threshold and set to false whenever the laser bias current is above the low-alarm-threshold";
            }
            leaf low-alarm-threshold {
              type decimal64 {
                fraction-digits 3;
              }
              description
                "Read from the installed transceiver";
            }
            leaf high-warning-condition {
              type boolean;
              description
                "Set to true whenever the laser bias current is above the high-warning-threshold and set to false whenever the laser bias current is below the high-warning-threshold";
            }
            leaf high-warning-threshold {
              type decimal64 {
                fraction-digits 3;
              }
              description
                "Read from the installed transceiver";
            }
            leaf low-warning-condition {
              type boolean;
              description
                "Set to true whenever the laser bias current is below the low-warning-threshold and set to false whenever the laser bias current is above the low-warning-threshold";
            }
            leaf low-warning-threshold {
              type decimal64 {
                fraction-digits 3;
              }
              description
                "Read from the installed transceiver";
            }
          }
        }
      }
      container ethernet {
        leaf hw-mac-address {
          config false;
          type srl_nokia-comm:mac-address;
          description
            "The MAC address associated with the port";
        }
        container flow-control {
          leaf receive {
            type boolean;
            // default false;

            // flow control is not applicable for all interfaces, so default can not be applied here
            // The problem is, the information delivered to chassis mgr will always have the flow-control value set,
            // even if it's not explicitly configured, so there's no way for chassis mgr to tell if the user has
            // configured flow-control or not.
            // As a result, the only thing chassis mgr can do is verify that the flow-control value is default for
            // those interfaces that don't support its configuration.
            // But this is not acceptable because if the user configures the flow-control to the default on an
            // interface that doesn't support that configuration, then when you save the configuration, it will
            // explicitly write out that configured value.  If later in the future we decide to change the default
            // value, then we will no longer be able to load that configuration.  Whereas a saved config file where
            // flow-control is not explicitly configured will not specify a value, so it will always load in a newer
            // release of software even if the rules for what values are valid change.

            description
              "Enables/disables processing of received PAUSE frames";
            //TO-DO check that the interface is not loN
          }
        }
        leaf port-speed {
          config false;
          srl_nokia-ext:show-importance "high";
          type enumeration {
            enum "10M";
            enum "100M";
            enum "1G";
            enum "10G";
            enum "25G";
            enum "40G";
            enum "50G";
            enum "100G";
            enum "200G";
            enum "400G";
            enum "1T";
          }
          description
            "The speed of the port or channel

            If no value is configured, the value is read from hardware.

            If a value is configured but the interface corresponds to a slot with no IMM, or an MDA slot with no MDA, or a connector with no transceiver  the value is accepted without  checking or restriction and it will be displayed as the operational (state) value.

            If a value is configured and the interface corresponds to an installed IMM, MDA (if applicable) and connector and the port-speed is supported by the installed transceiver then the value is accepted and it will be displayed as the operational (state) value.

            If a value is configured and the interface corresponds to an installed IMM, MDA (if applicable) and connector and the port-speed is NOT supported by the installed transceiver then the port is forced operationally down.";
        }
        container statistics {
          config false;
          /* leaf in-mac-control-frames {
            type srl_nokia-comm:zero-based-counter64;
            description
              "Number of MAC layer control frames received on the interface.";
          } */
          leaf in-mac-pause-frames {
            type srl_nokia-comm:zero-based-counter64;
            description
              "Number of MAC layer PAUSE frames received on the interface.";
          }
          leaf in-oversize-frames {
            type srl_nokia-comm:zero-based-counter64;
            description
              "Number of oversize frames received on the interface (i.e. frames that exceed the operational port MTU)";
          }
          leaf in-jabber-frames {
            type srl_nokia-comm:zero-based-counter64;
            description
              "Number of jabber frames received on the interface. Jabber frames are typically defined as oversize frames which also have a bad CRC.";
          }
          leaf in-fragment-frames {
            type srl_nokia-comm:zero-based-counter64;
            description
              "Number of fragment frames received on the interface.";
          }
          leaf in-crc-error-frames {
            type srl_nokia-comm:zero-based-counter64;
            description
              "Number of receive error events due to FCS/CRC check failure.";
          }
          /* leaf out-mac-control-frames {
            type srl_nokia-comm:zero-based-counter64;
            description
              "Number of MAC layer control frames sent on the interface.";
          } */
          /* leaf out-mac-pause-frames {
            type srl_nokia-comm:zero-based-counter64;
            description
              "Number of MAC layer PAUSE frames sent on the interface.";
          } */
          leaf in-64b-frames {
            type srl_nokia-comm:zero-based-counter64;
            description
              "Number of received Ethernet frames that are exactly 64 bytes in length";
          }
          leaf in-65b-to-127b-frames {
            type srl_nokia-comm:zero-based-counter64;
            description
              "Number of received Ethernet frames that are 65-127 bytes in length";
          }
          leaf in-128b-to-255b-frames {
            type srl_nokia-comm:zero-based-counter64;
            description
              "Number of received Ethernet frames that are 128-255 bytes in length";
          }
          leaf in-256b-to-511b-frames {
            type srl_nokia-comm:zero-based-counter64;
            description
              "Number of received Ethernet frames that are 256-511 bytes in length";
          }
          leaf in-512b-to-1023b-frames {
            type srl_nokia-comm:zero-based-counter64;
            description
              "Number of received Ethernet frames that are 512-1023 bytes in length";
          }
          leaf in-1024b-to-1518b-frames {
            type srl_nokia-comm:zero-based-counter64;
            description
              "Number of received Ethernet frames that are 1024-1518 bytes in length";
          }
          leaf in-1519b-or-longer-frames {
            type srl_nokia-comm:zero-based-counter64;
            description
              "Number of received Ethernet frames that are 1519 bytes or longer";
          }
          leaf out-64b-frames {
            type srl_nokia-comm:zero-based-counter64;
            description
              "Number of transmitted Ethernet frames that are exactly 64 bytes in length";
          }
          leaf out-65b-to-127b-frames {
            type srl_nokia-comm:zero-based-counter64;
            description
              "Number of transmitted Ethernet frames that are 65-127 bytes in length";
          }
          leaf out-128b-to-255b-frames {
            type srl_nokia-comm:zero-based-counter64;
            description
              "Number of transmitted Ethernet frames that are 128-255 bytes in length";
          }
          leaf out-256b-to-511b-frames {
            type srl_nokia-comm:zero-based-counter64;
            description
              "Number of transmitted Ethernet frames that are 256-511 bytes in length";
          }
          leaf out-512b-to-1023b-frames {
            type srl_nokia-comm:zero-based-counter64;
            description
              "Number of transmitted Ethernet frames that are 512-1023 bytes in length";
          }
          leaf out-1024b-to-1518b-frames {
            type srl_nokia-comm:zero-based-counter64;
            description
              "Number of transmitted Ethernet frames that are 1024-1518 bytes in length";
          }
          leaf out-1519b-or-longer-frames {
            type srl_nokia-comm:zero-based-counter64;
            description
              "Number of transmitted Ethernet frames that are 1519 bytes or longer";
          }
          leaf last-clear {
            type srl_nokia-comm:date-and-time-delta;
            description
              "Timestamp of the last time the MAC counters were cleared.";
          }
        }
      }
      uses subinterface-top;
    }
  }

  uses interface-top;
}
