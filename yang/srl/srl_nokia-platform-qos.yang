module srl_nokia-platform-qos {
  yang-version 1.1;
  namespace "urn:srl_nokia/platform-qos";
  prefix srl_nokia-platform-qos;

  import srl_nokia-common { prefix srl_nokia-comm; }
  import srl_nokia-platform {prefix srl_nokia-platform; }
  import srl_nokia-platform-lc {prefix srl_nokia-platform-lc; }
  import srl_nokia-platform-resource-monitoring {prefix srl_nokia-platform-res-mon; }

  description
    "This module defines configuration and operational state related to QoS resources in the system";

  revision 2019-11-30 {
    description
      "SRLinux 19.11.1";
  }

  identity qos-resources {
    description
      "Base type for QoS resources";
  }

  identity classifier-profiles {
    base qos-resources;
    description
      "A classifier-profile resource is used every time a different combination of DSCP classifier and MPLS-TC classifier is applied to an ingress subinterface of the forwarding complex. There are 16 of these resources and one is always used by the combination of the default DSCP classifier and the default MPLS TC classifier.";
  }

  identity rewrite-profiles {
    base qos-resources;
    description
      "A rewrite-profile resource is used every time a different combination of DSCP rewrite-rule and MPLS-TC rewrite-rule is applied to an egress subinterface of the forwarding complex. There are 32 of these resources.";
  }

  grouping qos-resource-monitoring {
    container qos {
      list resource {
        key name;
        leaf name {
          type identityref  {
            base qos-resources;
          }
          description
            "The name of the QoS resource";
        }
        leaf rising-threshold-log {
          type srl_nokia-comm:percentage;
          default "90";
          description
            "Sets the threshold that triggers the generation of a WARNING log whenever the utilization of the QoS resource in any linecard/complex/core reaches this value in a rising direction";
        }
        leaf falling-threshold-log {
          type srl_nokia-comm:percentage;
          default "70";
          description
            "Sets the threshold that triggers the generation of a NOTICE log whenever the utilization of the QoS resource in any linecard/complex/core falls reaches this value in a falling direction";
        }
      }
    }
  }

  grouping qos-utilization {
    container qos {
      config false;
      list resource {
        key name;
        leaf name {
          type identityref  {
            base qos-resources;
          }
          description
            "The name of the QoS resource";
        }
        leaf used {
          type uint16;
          description
            "The number of resources that are in use";
        }
        leaf free {
          type uint16;
          description
            "The number of resources that are unused and available";
        }
      }
    }
  }

  grouping buffer-memory {
    container buffer-memory {
      description
        "Container for utilization statistics of the packet buffer memory";
      config false;
      container sram {
        description
          "Container for utilization statistics of the on-chip SRAM memory.";
        leaf used {
          type uint64;
          units "bytes";
          description
            "Used SRAM memory";
        }
        leaf free {
          type uint64;
          units "bytes";
          description
            "Available SRAM memory";
        }
      }
      container dram {
        description
          "Container for utilization statistics of the DRAM memory.";
                leaf used {
          type srl_nokia-comm:percentage;
          description
            "Used DRAM memory";
        }
      }
    }
  }


  augment "/srl_nokia-platform:platform/srl_nokia-platform-res-mon:resource-monitoring" {
    uses qos-resource-monitoring;
  }

  augment "/srl_nokia-platform:platform/srl_nokia-platform-lc:linecard/srl_nokia-platform-lc:forwarding-complex" {
    uses qos-utilization;
  }

  augment "/srl_nokia-platform:platform/srl_nokia-platform-lc:linecard/srl_nokia-platform-lc:forwarding-complex" {
    uses buffer-memory;
  }

}
