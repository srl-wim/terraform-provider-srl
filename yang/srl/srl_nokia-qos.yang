module srl_nokia-qos {
  yang-version 1.1;
  namespace "urn:srl_nokia/qos";
  prefix "srl_nokia-qos";

  import srl_nokia-common { prefix srl_nokia-comm; }
  import srl_nokia-interfaces { prefix srl_nokia-if; }

  revision 2019-11-30 {
    description
      "SRLinux 19.11.1";
  }

  typedef traffic-class {
    type uint8 {
      range "0..7";
    }
  }

  typedef forwarding-class {
    type enumeration {
      enum "fc0";
      enum "fc1";
      enum "fc2";
      enum "fc3";
      enum "fc4";
      enum "fc5";
      enum "fc6";
      enum "fc7";
    }
  }

  typedef dscp-name {
    type enumeration {
      enum "CS0" { value 0; }
      enum "CS1" { value 8; }
      enum "AF11" { value 10; }
      enum "AF12" { value 12; }
      enum "AF13" { value 14; }
      enum "CS2" { value 16; }
      enum "AF21" { value 18; }
      enum "AF22" { value 20; }
      enum "AF23" { value 22; }
      enum "CS3" { value 24; }
      enum "AF31" { value 26; }
      enum "AF32" { value 28; }
      enum "AF33" { value 30; }
      enum "CS4" { value 32; }
      enum "AF41" { value 34; }
      enum "AF42" { value 36; }
      enum "AF43" { value 38; }
      enum "CS5" { value 40; }
      enum "EF" { value 46; }
      enum "CS6" { value 48; }
      enum "CS7" { value 56; }
    }
  }

  grouping qos-top {
    description
      "Top-level grouping for QoS model";

    container qos {
      description
        "Top-level container for QoS data";
      uses qos-classifier-top;
      uses qos-rewrite-top;
    }
  }

  grouping qos-classifier-top {
    description
      "Top-level grouping for classifier data";

    container classifiers {
      uses dscp-classifier;
      uses mpls-tc-classifier;
    }
  }

  grouping dscp-classifier {
    list dscp-policy {
      key name;
      leaf name {
        type srl_nokia-comm:name;
        description
          "User-configured name for a DSCP classification policy

          The name 'default' is reserved for the system default DSCP classifier.";
      }
      list dscp {
        key value;
        leaf value {
          type uint8 {
            range "0..63";
          }
          description
            "DSCP codepoint value, expressed as a number in the range 0-63";
        }
        leaf forwarding-class {
          type forwarding-class;
          description
            "The forwarding class to which the DSCP value is mapped";
        }
      }
    }
  }

  grouping mpls-tc-classifier {
    list mpls-traffic-class-policy {
      key name;
      leaf name {
        type srl_nokia-comm:name;
        description
          "User-configured name for an MPLS traffic-class classification policy

          The name 'default' is reserved for the system default MPLS TC classifier.";
      }
      list traffic-class {
        key value;
        leaf value {
          type traffic-class;
          description
            "A single traffic-class value";
        }
        leaf forwarding-class {
          type forwarding-class;
          description
            "The forwarding class to which the traffic-class value is mapped";
        }
      }
    }
  }

  grouping qos-rewrite-top {
    description
      "Top-level grouping for classifier data";

    container rewrite-rules {
      uses dscp-rewrite;
      uses mpls-tc-rewrite;
    }
  }

  grouping dscp-rewrite {
    list dscp-policy {
      key name;
      leaf name {
        type srl_nokia-comm:name;
        description
          "User-configured name for a DSCP rewrite policy.";
      }
      list map {
        key forwarding-class;
        leaf forwarding-class {
          type forwarding-class;
          description
            "The forwarding-class value";
        }
        leaf dscp {
          type union {
            type uint8 {
              range "0..63";
            }
            type dscp-name;
          }
        }
      }
    }
  }

  grouping mpls-tc-rewrite {
    list mpls-traffic-class-policy {
      key name;
      leaf name {
        type srl_nokia-comm:name;
        description
          "User-configured name for an MPLS traffic-class rewrite policy.";
      }
      list map {
        key forwarding-class;
        leaf forwarding-class {
          type forwarding-class;
          description
            "The forwarding-class value";
        }
        leaf traffic-class {
          type traffic-class;
          description
            "The MPLS traffic class value to mark the packet with";
        }
      }
    }
  }

  grouping port-qos {
    container qos {
      container output {
        list queue {
          description "List of per-port queues.";
          key queue-id;
          leaf queue-id {
            type srl_nokia-comm:queue-index;
            description
              "The queue identifier

              The queue ID indicates the forwarding-class that is mapped to the queue.";
          }
          container queue-scheduler {
            leaf strict-priority {
              type boolean;
              default true;
              description
                "When set to true the queue is serviced as a strict priority queue. When set to false the queue is serviced using WRR, even if the queue does not have a configured weight.";
            }
            leaf weight {
              type uint64 {
                range "1..255";
              }
              description
                "Configures the relative weight of a round-robin queue";
              // must "not(../strict-priority = 'true')"
            }
          }
        }
      }
    }
  }

  grouping queue-stats {
      container queue-statistics {
          config false;
          list queue {
              key "queue-id";
              description
                  "List of output queues associated with the physical port.";
              leaf queue-id {
                  type srl_nokia-comm:queue-index;
                  description
                      "Queue number: 0-7";
              }
              leaf transmitted-packets {
                  type srl_nokia-comm:zero-based-counter64;
                  description
                      "Number of packets transmitted by the egress queue, including transit traffic and locally-originated traffic. This measures packets transmitted on the wire after drops in the VOQ queues, drops done by ACL entries and final drops by the EGQ itself (e.g. due to header compensation issues).";
              }
              leaf transmitted-octets {
                  type srl_nokia-comm:zero-based-counter64;
                  description
                      "Number of octets transmitted by this egress queue, counted as described above.";
              }
              leaf final-dropped-packets {
                  type srl_nokia-comm:zero-based-counter64;
                  description
                      "Number of packets dropped by the egress queue itself, for example due to header compensation issues. These drops do not result from congestion.";
              }
              leaf final-dropped-octets {
                  type srl_nokia-comm:zero-based-counter64;
                  description
                      "Number of octets in packets dropped by the egress queue itself.";
              }
              list virtual-output-queue {
                  description
                      "List of virtual output queues that can send traffic to this egress queue. The list always has one entry for each IMM slot in the chassis, even if one or more slots are empty.";
                  key slot;
                  leaf slot {
                      type uint8 {
                          range "1..8";
                      }
                      description
                          "The slot identifier for the virtual output queue.";
                  }
                  leaf forwarded-packets {
                      type srl_nokia-comm:zero-based-counter64;
                      description
                          "The number of packets transmitted from the VOQ to the egress queue. This reads 0 when the IMM associated with the VOQ is not inserted and it resets to 0 whenever the IMM associated with the VOQ is removed.";
                  }
                  leaf forwarded-octets {
                      type srl_nokia-comm:zero-based-counter64;
                      description
                          "The number of octets in packets transmitted from the VOQ to the egress queue.";
                  }
                  leaf dropped-packets {
                      type srl_nokia-comm:zero-based-counter64;
                      description
                          "The number of packets dropped in the VOQ due to congestion at the egress port/queue.";
                  }
                  leaf dropped-octets {
                      type srl_nokia-comm:zero-based-counter64;
                      description
                          "The number of octets in packets dropped in the VOQ due to congestion at the egress port/queue.";
                  }
              }
              leaf last-clear {
                  type srl_nokia-comm:date-and-time-delta;
                  description
                      "Timestamp of the last time the queue statistics were cleared";
              }
          }
      }
  }

  grouping subinterface-qos {
    container qos {
      container input {
        container classifiers {
          leaf ipv4-dscp {
            type leafref {
                path "/srl_nokia-qos:qos/srl_nokia-qos:classifiers/srl_nokia-qos:dscp-policy/name";
            }            
            description "Reference to the name of a DSCP classifier policy";
          }
          leaf ipv6-dscp {
            type leafref {
                path "/srl_nokia-qos:qos/srl_nokia-qos:classifiers/srl_nokia-qos:dscp-policy/name";
            }            
            description "Reference to the name of a DSCP classifier policy";
          }
          leaf mpls-traffic-class {
            type leafref {
                path "/srl_nokia-qos:qos/srl_nokia-qos:classifiers/srl_nokia-qos:mpls-traffic-class-policy/name";
            }            
            description "Reference to the name of an MPLS traffic-class classifier policy";
          }
        }
      }
      container output {
        container rewrite-rules {
          leaf ipv4-dscp {
            type leafref {
                path "/srl_nokia-qos:qos/srl_nokia-qos:rewrite-rules/srl_nokia-qos:dscp-policy/name";
            }            
            description "Reference to the name of a DSCP rewrite-rule policy";
          }
          leaf ipv6-dscp {
            type leafref {
                path "/srl_nokia-qos:qos/srl_nokia-qos:rewrite-rules/srl_nokia-qos:dscp-policy/name";
            }            
            description "Reference to the name of a DSCP rewrite-rule policy";
          }
          leaf mpls-traffic-class {
            type leafref {
                path "/srl_nokia-qos:qos/srl_nokia-qos:rewrite-rules/srl_nokia-qos:mpls-traffic-class-policy/name";
            }            
            description "Reference to the name of an MPLS traffic-class rewrite-rule policy";
          }
        }
      }
    }
  }

  uses qos-top;

  augment "/srl_nokia-if:interface" {
      uses port-qos;
  }

   augment "/srl_nokia-if:interface" { 
       uses queue-stats;
   }

  augment "/srl_nokia-if:interface/srl_nokia-if:subinterface" {
      uses subinterface-qos;
  }

}
