module srl_nokia-configuration {
  yang-version 1.1;
  namespace "urn:srl_nokia/configuration";
  prefix srl-config;

  import srl_nokia-system {
    prefix srl-system;
  }
  import srl_nokia-common {
    prefix srl-comm;
  }

  description
    "This module defines configuration and operational state data related to the system configuration.";

  revision 2019-11-30 {
    description
      "SRLinux 19.11.1";
  }

  typedef candidate-type {
    type enumeration {
      enum shared;
      enum private;
      enum exclusive;
    }
  }

  grouping configuration-state-sessions-top {
    description
      "State data related to configuration sessions";
    list session {
      config false;
      description
        "List of configuration sessions currently active";
      key "id";
      leaf id {
        type uint32;
        description
          "System generated ID for the configuration session";
      }
      leaf type {
        type candidate-type;
        description
          "Type of configuration session";
      }
      leaf username {
        type string;
        description
          "User that started the configuration session";
      }
      leaf started {
        type srl-comm:date-and-time-delta;
        description
          "Start date and time of the configuration session";
      }
    }
  }

  grouping configuration-checkpoints-top {
    description
      "Configuration data related to checkpoints";
    leaf max-checkpoints {
      type uint8;
      default "10";
      description
        "The number of checkpoints kept by the system";
    }
  }

  grouping configuration-state-checkpoints-top {
    description
      "State data related to checkpoints";
    list checkpoint {
      config false;
      description
        "List of current checkpoints present in the system";
      key "id";
      leaf id {
        type uint8;
        description
          "System generated ID for the checkpoint";
      }
      leaf name {
        type string;
        description
          "User provided name of the checkpoint";
      }
      leaf comment {
        type string;
        description
          "User provided annotations associated with the checkpoint";
      }
      leaf created {
        type srl-comm:date-and-time-delta;
        description
          "Date and time this checkpoint was created";
      }
      leaf version {
        type string;
        description
          "System version that the checkpoint was generated on";
      }
      leaf username {
        type string;
        description
          "Username that created this checkpoint";
      }
      leaf size {
        type uint64;
        description
          "Size of the checkpoint configuration file";
        units "bytes";
      }
    }
  }

  grouping configuration-top {
    container configuration {
      description
        "Top-level container for configuration and state data related to the system configuration";
      leaf last-change {
        config false;
        type srl-comm:date-and-time-delta;
        description
          "Date and time of the last successful commit";
      }
      uses configuration-checkpoints-top;
      uses configuration-state-checkpoints-top;
      uses configuration-state-sessions-top;
    }
  }

  augment "/srl-system:system" {
    uses configuration-top;
  }
}
