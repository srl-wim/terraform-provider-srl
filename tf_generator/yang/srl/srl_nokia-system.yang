module srl_nokia-system {
  yang-version 1.1;

  // namespace

  namespace "urn:srl_nokia/system";
  prefix srl_nokia-system;

  description
    "This module defines configuration and operational state data
     related to system management

     Portions of this model reuse data definitions or structure from
     RFC 7317 - A YANG Data Model for System Management";

  revision 2019-11-30 {
    description
      "SRLinux 19.11.1";
  }

  container system {
    description
      "Enclosing container for system management.";
    presence "Configure system";
    leaf-list trace-options {
      description
        "Management server trace options";
      type enumeration {
        enum request;
        enum response;
        enum common;
      }
    }
  }
}
