module srl_nokia-network-instance {

  yang-version 1.1;

  // namespace
  namespace "urn:srl_nokia/network-instance";

  prefix "srl_nokia-netinst";

  import srl_nokia-common { prefix srl_nokia-comm; }
  import srl_nokia-icmp { prefix srl_nokia-icmp; }

  description
    "This yang file gives a description of a network-instance. This may be a Layer 3 forwarding construct such as a virtual routing and forwarding (VRF) instance, or a Layer 2 instance such as a virtual switch instance (VSI). Mixed Layer 2 and Layer 3 instances are also supported.";


  revision 2019-11-30 {
    description
      "SRLinux 19.11.1";
  }

  typedef network-instance-subintf-ref {
    type srl_nokia-comm:subinterface-all;
    description
      "Reference type to a specific subinterface of the form <interface-name>.<subinterface-index>";
  }

  identity ni-type {
    description
      "Base type for network instance types.";
  }

  identity default {
    base ni-type;
    description
      "A special routing instance which acts as the 'default' or 'global' routing instance for a network device.";
  }

  identity ip-vrf {
    base ni-type;
    description
      "A private Layer 3 only routing instance.";
  }

  grouping network-instance-top {
    description
      "Top-level grouping containing a list of network instances.";

    list network-instance {
      key "name";
      max-elements "16";
      description "Network instances configured on the local system";

      leaf name {
        type srl_nokia-comm:name;
        description
            "A unique name identifying the network instance";
      }

      leaf type {
        type identityref {
          base ni-type;
        }
        default "default";
        description
          "The type of network instance. The value of this leaf
           indicates the type of forwarding entries that should be
           supported by this network instance";
      }

      leaf admin-state {
        type srl_nokia-comm:admin-state;

        default "enable";
        description
          "This leaf contains the configured, desired state of the
           network instance.";
      }
      leaf oper-state {
        config false;
        type srl_nokia-comm:oper-state;
        description
          "This leaf contains the operational state of the network instance.";
      }

      leaf description {
        type srl_nokia-comm:description;
        description
          "A user-entered description of this network instance.";
      }

      leaf router-id {
        type srl_nokia-comm:dotted-quad;
        description
          "A identifier for the local network instance - typically
           used within associated routing protocols or signalling
           routing information in another network instance";
      }

      container ip-forwarding {
        description
          "Forwarding options that apply to the entire network instance.";
        leaf receive-ipv4-check {
          type boolean;
          default true;
          description
            "If set to true then the following check is done on every subinterface of the network-instance: if an IPv4 packet is received on a subinterface and the IPv4 oper-status of this subinterface is down the packet is discarded. If this leaf is set to false then received IPv4 packets are accepted on all subinterfaces of the network-instance that are up, even if they do not have any IPv4 addresses.";
        }
        leaf receive-ipv6-check {
          type boolean;
          default true;
          description
            "If set to true then the following check is done on every subinterface of the network-instance: if an IPv6 packet is received on a subinterface and the IPv6 oper-status of this subinterface is down the packet is discarded. If this leaf is set to false then received IPv6 packets are accepted on all subinterfaces of the network-instance that are up, even if they do not have any IPv6 addresses.";
        }
      }

      container ip-load-balancing {
        description
          "Container for IP load-balancing options that are specific to the network-instance";
        list resilient-hash-prefix {
          description
            "List of IPv4 and IPv6 prefixes which should be programmed for resilient ECMP hashing.";
          key ip-prefix;
          leaf ip-prefix {
            type srl_nokia-comm:ip-prefix;
            description
              "IPv4 or IPv6 prefix. Active routes in the FIB that exactly match this prefix or that are longer matches of this prefix are provided with resilient-hash programming.";
          }
          leaf hash-buckets-per-path {
            type uint8 {
              range "1..32";
            }
            default 1;
            description
              "The number of times each next-hop is repeated in the fill pattern if there are max-paths ECMP next-hops

              A larger number consumes more resources but provides more granularity when flows need to be moved. Note that hash-buckets-per-path * max-paths must be less than or equal to 128.";
          }
          leaf max-paths {
            type uint8 {
              range "1..64";
            }
            default 1;
            description
              "The maximum number of ECMP next-hops per route associated with the resilient-hash prefix

              If a matching route has more than this number of ECMP next-hops only the first N are used, where N is the value of this parameter. Note that hash-buckets-per-path * max-paths must be less than or equal to 128.";
          }
        }
      }

      list interface {
        key "name";

        description "List of subinterfaces used by this network-instance";

        leaf name {
          type srl_nokia-netinst:network-instance-subintf-ref;
          description
            "Identifier of sub-interface used in this network-instance";
        }
        leaf oper-state {
          config false;
          type srl_nokia-comm:oper-state;
          description
            "The operational state of this subinterface.";
        }
        leaf oper-down-reason {
          config false;
          type enumeration {
            enum "ip-addr-missing";
            enum "ip-addr-overlap";
            enum "subif-down";
            enum "net-inst-down";
          }
          description
            "The reason for the interface being down in the network-instance";
        }
      }

      // Hook icmp and icmp6 containers
      uses srl_nokia-icmp:icmp-top;
      uses srl_nokia-icmp:icmp6-top;

      container protocols {
        description
          "The routing protocols that are enabled for this
           network-instance.";

        // Protocols are augmented into this spot
      }

      container route-table {
          config false;
      }
    }
  }

  uses network-instance-top;
}
