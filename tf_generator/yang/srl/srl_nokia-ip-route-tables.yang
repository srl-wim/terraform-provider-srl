module srl_nokia-ip-route-tables {
  yang-version 1.1;

  namespace "urn:srl_nokia/ip-route-tables";
  prefix srl_nokia-ip-route-tables;

  import srl_nokia-common { prefix srl_nokia-comm; }
  import srl_nokia-extensions { prefix srl_nokia-ext; }
  import srl_nokia-network-instance { prefix srl_nokia-netinst; }
  import srl_nokia-interfaces { prefix srl_nokia-if; }

  description
    "A model describing the IP routing tables of a network instance.";

  revision 2019-11-30 {
    description
      "SRLinux 19.11.1";
  }

  identity fib-nexthop-type {
    description
      "Base type for next-hop object types.";
  }

  identity extract {
    base fib-nexthop-type;
    description
      "Next-hop will cause matching packets to be delivered to the CPM.";
  }

  identity direct {
    base fib-nexthop-type;
    description
      "Next-hop was resolved by a local route - i.e. it is an address on a connected subnet.";
  }

  identity discard {
    base fib-nexthop-type;
    description
      "Next-hop will cause matching packets to be dropped without ICMP generation.";
  }

  identity reject {
    base fib-nexthop-type;
    description
      "Next-hop will cause matching packets to be dropped with ICMP generation.";
  }

  identity indirect {
    base fib-nexthop-type;
    description
      "Next-hop was resolved by a non-local route - i.e. it is not an address on a connected subnet.";
  }

  identity tunnel {
    base fib-nexthop-type;
    description
      "Next-hop was resolved by a tunnel.";
  }

  grouping ipv4-ipv6-entry-common-fields {
    leaf owner {
      type identityref {
        base srl_nokia-comm:ip-route-owner;
      }
      srl_nokia-ext:show-importance "high";
      description
        "The protocol or application that owns the IP route";
    }
    leaf metric {
      type uint32;
      srl_nokia-ext:show-importance "high";
      description
        "The metric of the IP route. In general, when comparing two routes with the same owner and preference, the route with the lower metric is the one that is activated and used for forwarding.";
    }
    leaf preference {
      type uint8;
      srl_nokia-ext:show-importance "high";
      description
        "The IP route table preference. This is sometimes called the administrative distance of the route. In general, when comparing any two routes, the route with the lower preference is the one that is activated and used for forwarding.";
    }
    leaf active {
      type boolean;
      srl_nokia-ext:show-importance "high";
      description
        "If set to true then the route is installed as the active route for the IP prefix in the FIB. A route can be inactive because there is a more preferred route for the same prefix or else its next-hops are unresolved.";
    }
    leaf last-app-update {
      type srl_nokia-comm:date-and-time-delta;
      description
        "The date and time of the last update of this route by the owning application or protocol.";
    }
    leaf fib-change-pending {
      type boolean;
      description
        "If set to true then a create, delete or update of the route by its owner application has occurred recently but not all linecards have acknowledged the change yet.";
    }
    leaf next-hop-group {
      type leafref {
        path "/srl_nokia-netinst:network-instance/srl_nokia-netinst:route-table/srl_nokia-ip-route-tables:next-hop-group/srl_nokia-ip-route-tables:index";
      }
      description "The next-hop-group indirection object used by this route.";
    }
    leaf resilient-hash {
      type boolean;
      description
        "Set to true if the route is covered by a resilient-hash-prefix entry";
    }
    container fib-programming {
      description
        "Container for state related to the FIB programming of the route";
      leaf status {
        type enumeration {
          enum "success" {
            description
              "The route was successfully programmed into the FIB table of all linecards.";
          }
          enum "failed" {
            description
              "The was not programmed into the FIB table of one or more linecards due to the FIB table being full.";
          }
        }
        description
          "The status of the FIB programming";
      }
      leaf-list failed-slots {
        type uint8 {
          range "1..8";
        }
        description
          "The list of slot IDs corresponding to the linecards that did not successfully program the route due to the FIB table being full";
      }
    }
  }

  grouping ip-table-statistics {
    container statistics {
      leaf active-entries {
        type srl_nokia-comm:zero-based-counter64;
        description
          "The total number of entries that are active in the FIB.";
      }
      leaf active-entries-with-ecmp {
        type srl_nokia-comm:zero-based-counter64;
        description
          "The total number of entries that are active in the FIB and that have multiple ECMP next-hops.";
      }
      leaf total-entries {
        type srl_nokia-comm:zero-based-counter64;
        description
          "The total number of routes, active and inactive, belonging to this address family, that are present in the routing table.";
      }
    }
  }

  grouping ip-tables-top {
    container ipv4-unicast {
      description
        "The container for the IPv4 unicast routing table of the network instance.";
      list route {
        key "ipv4-prefix id";
        leaf ipv4-prefix {
          type srl_nokia-comm:ipv4-prefix;
        }
        leaf id {
          type uint16;
          description
            "An index value representing the relative order of preference of routes for the same prefix. If there is an active route for the prefix it will always be assigned index 0. The route with index 1 is next in order to become active if the route with index 0 is removed.";
        }
        uses ipv4-ipv6-entry-common-fields;
      }
      uses ip-table-statistics;
    }
    container ipv6-unicast {
      description
        "The container for the IPv6 unicast routing table of the network instance.";
      list route {
        key "ipv6-prefix id";
        leaf ipv6-prefix {
          type srl_nokia-comm:ipv6-prefix;
        }
        leaf id {
          type uint16;
          description
            "An index value representing the relative order of preference of routes for the same prefix. If there is an active route for the prefix it will always be assigned index 0. The route with index 1 is next in order to become active if the route with index 0 is removed.";
        }
        uses ipv4-ipv6-entry-common-fields;
      }
      uses ip-table-statistics;
    }
  }

  grouping next-hops-top {
    list next-hop-group {
      key index;
      leaf index {
        type uint64;
        description
          "A system-wide unique identifier of a next-hop-group indirection object (system allocated).";
      }
      leaf owner {
        type identityref {
          base srl_nokia-comm:nhg-owner;
        }
        description
          "The protocol or application that owns the next-hop-group programming.";
      }
      leaf last-app-update {
        type srl_nokia-comm:date-and-time-delta;
        description
          "The date and time of the last update of this next-hop-group by the owning application or protocol.";
      }
      list next-hop {
        key id;
        leaf id {
          type uint16 {
            range 0..1023;
          }
          description
            "A unique identifier of a next-hop member (system allocated).";
        }
        leaf next-hop {
          type leafref {
            path "/srl_nokia-netinst:network-instance/srl_nokia-netinst:route-table/srl_nokia-ip-route-tables:next-hop/srl_nokia-ip-route-tables:index";
          }
        }
        leaf active {
          type boolean;
          description
            "If set to true then the next-hop is active and used in the group. It can be inactive if it is not resolved";
        }
      }
    }
    list next-hop {
      key index;
      leaf index {
        type uint64;
        description
          "A system-wide unique identifier of a next-hop object (system allocated).";
      }
      leaf type {
        type identityref {
          base fib-nexthop-type;
        }
        srl_nokia-ext:show-importance "high";
        description
          "The next-hop type used by the datapath.";
      }
      leaf ip-address {
        type srl_nokia-comm:ip-address;
        srl_nokia-ext:show-importance "high";
        description
          "The next-hop IP address. Only populated when the next-hop type is indirect or tunnel.";
      }
      leaf subinterface {
        type leafref {
          path "/srl_nokia-if:interface/srl_nokia-if:subinterface/srl_nokia-if:name";
        }
        srl_nokia-ext:show-importance "high";
        description
          "The next-hop interface. Only populated when the next-hop type is direct.";
      }
      container resolving-route {
        leaf ip-prefix {
          type srl_nokia-comm:ip-prefix;
          description
            "The prefix of the resolving route.";
        }
        leaf owner {
          type identityref {
            base srl_nokia-comm:ip-route-owner;
          }
          description
            "The owner of the resolving route.";
        }
      }
      leaf-list pushed-mpls-label-stack {
        type srl_nokia-comm:mpls-label;
        max-elements 1;
        description
          "The list of MPLS labels to push onto the packet when forwarding to this particular next-hop.";
      }
      leaf encapsulate-header {
        type enumeration {
          enum gre { value 1; }
          enum ipv4 { value 2; }
          enum ipv6 { value 3; }
          enum mpls { value 4; }
        }
        description
          "The type of tunneling encapsulation that is applied to packets forwarded to this next-hop.";
      }
    }
  }
  augment "/srl_nokia-netinst:network-instance/srl_nokia-netinst:route-table" {
    uses ip-tables-top;
    uses next-hops-top;
  }
}
