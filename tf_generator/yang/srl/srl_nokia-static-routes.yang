module srl_nokia-static-routes {

    yang-version 1.1;

    // namespace
    namespace "urn:srl_nokia/static-routes";

    prefix "srl_nokia-static-routes";

    import srl_nokia-common { prefix srl_nokia-comm; }
    import srl_nokia-network-instance { prefix srl_nokia-netinst; }
    import srl_nokia-next-hop-groups { prefix srl_nokia-nhg; }

    description
        "This yang file gives a description of static route configuration.";

    revision 2019-11-30 {
    description
      "SRLinux 19.11.1";
  }

    grouping static-route-top {
        container static-routes {
            presence "Configure Static Routes";
            list route {
                max-elements 16384;
                key "prefix";
                leaf prefix {
                    type srl_nokia-comm:ip-prefix;
                }
                leaf admin-state {
                    type srl_nokia-comm:admin-state;
                    default "enable";
                    description
                        "Used to disable the  static route.";
                }
                leaf metric {
                    type uint32;
                    default "1";
                    description
                        "IGP metric of the static route.";
                }
                leaf preference {
                    type uint8 {
                        range "0..255";
                    }
                    default 5;
                    description
                        "Route preference with lower values indicating a higher degree of preference.";
                }
                leaf next-hop-group {
                    type leafref {
                        path "../../../srl_nokia-nhg:next-hop-groups/srl_nokia-nhg:group/srl_nokia-nhg:name";
                    }
                }
                leaf installed {
                    config false;
                    type boolean;
                    description
                        "If set to true, this indicates that the static route was installed into the datapath. If this is false then there are 3 possible reasons:
                        (a) the admin-state is disable
                        (b) there is another IP route for the same prefix that has a superior preference
                        (c) the next-hop-group has no resolvable next-hops";
                }
            }
        }
    }
    augment "/srl_nokia-netinst:network-instance" {
        uses static-route-top;
    }
}
